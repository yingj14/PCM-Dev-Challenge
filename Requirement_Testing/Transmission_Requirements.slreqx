# Transmission_Requirements

## #1: Gear Selection Safety (Functional)
| The transmission controller shall permit gear selection only when operating conditions are valid for the requested gear. |
| --- |

### #2: Park Engagement (Functional)
| The transmission controller shall permit engagement of PARK only when \|vehSpd\| < 0.1 m/s |
| --- |

### #14 (Functional)

### #15 (Functional)

### #16: Gear Shift - Reverse (Functional)
The transmission controller shall permit REVERSE only when the vehicle speed is less than 0.5 m/s.
- Rationale: This prevents REVERSE from engaging while the vehicle is moving forward too quickly.

### #17: Neutral Gear Availability (Functional)
The transmission controller shall permit NEUTRAL regardless of vehicle speed.

### #18: Gear Shift - DRIVE (Functional)
The transmission controller shall permit DRIVE only when the vehicle speed is greater than -0.5 m/s.
- Rationale: This prevents DRIVE from engaging while the vehicle is moving backward too quickly.

## #3: Engine Operating Limits (Functional)
| The transmission controller shall prevent operation of the engine outside its allowable operating range. |
| --- |

### #4: Maximum Engine Speed (Functional)
| The transmission controller shall prevent engine speed from exceeding 7250 RPM. |
| --- |
- Rationale: Higher engine speeds will cause the internal piston forces to excess material limitations.

### #12: Minimum Engine Speed (Functional)
The transmission contoller shall prevent the engine speed from falling below 800 RPM during engine oerations.
- Rationale: Engine speeds below 800 RPM are outside the specified operating range and may cause the engine to stall or operate unstably.

## #9: Driver Request Handling (Functional)
| The transmission controller shall process driver gear requests according to transmission operating constraints. |
| --- |

### #10: Park Request Protection (Functional)
The transmission controller shall always command neutral when park is selected
- Rationale: If the transmission is in any drive or reverse gears it will cause undue strain on the engine and torque converter.

#### #25: Valid Drive Request Response (Functional)

#### #26: Invalid Drive Request Response (Functional)

### #22: Drive Request Handling (Functional)

#### #27: Valid Reverse Request Response (Functional)

#### #28: Invalid Reverse Request Response (Functional)

### #23: Reverse Request Handling (Functional)

### #24: Neutral Request Response (Functional)

## #11: Vehicle Performance (Functional)
The vehicle shall accelerate from 0 to 60 mph in less than 12 seconds when wide-open-throttle is applied (100% throttle)
- Rationale: If 0-60 acceleration time is greater than 12 seconds it will create unsafe situations on the road during merging and other high-acceleration manoeuvers.

## #19: Throttle Control (Functional)
The controller shall manage temporary throttle intervention for RPM matching during automatic shifts.
- Rationale: Supports smooth target gear engagement.

### #29: Throttle Modification Condition (Functional)
- Rationale: The controller shall modify DriverThrottle ONLY for RPM matching during an automatic gear shift.

### #30: Throttle Modification Duration (Functional)
Any throttle modification used for RPM matching shall end within 1 second of its initiation
- Rationale: Limits how long the controller overrides the driver.
